module arca-router {
  namespace "urn:arca:router:config:1.0";
  prefix "arca";

  import ietf-interfaces {
    prefix if;
  }

  import ietf-routing {
    prefix rt;
  }

  organization "Arca Router Project";
  contact "https://github.com/akam1o/arca-router";
  description
    "YANG data model for Arca Router - a Junos-like router implementation
     using VPP and FRR.

     This module defines the configuration and operational state for:
     - System settings (hostname)
     - v0.6 service, clustering, MPLS, VRRP, VPN, and QoS settings
     - Interface configuration (uses IETF interfaces model)
     - Routing configuration (uses IETF routing model with extensions)
     - BGP and OSPF protocol configuration";

  revision 2025-12-27 {
    description "Initial revision for Phase 3 Task 2.3";
    reference "PHASE3.md Task Group 2";
  }

  // ==================================================================
  // System Configuration
  // ==================================================================

  container system {
    description "System-level configuration";

    leaf host-name {
      type string {
        length "1..253";
        pattern '[a-zA-Z0-9]([a-zA-Z0-9\-]*[a-zA-Z0-9])?';
      }
      description "Router hostname (RFC 1123 compliant)";
    }

    container services {
      description "Local management and observability services.";

      container web-ui {
        description "Read-only Web UI service.";
        leaf enabled {
          type boolean;
          default false;
        }
        leaf listen-address {
          type string;
        }
        leaf port {
          type uint16;
        }
      }

      container prometheus {
        description "Prometheus metrics service.";
        leaf enabled {
          type boolean;
          default false;
        }
        leaf listen-address {
          type string;
        }
        leaf port {
          type uint16;
        }
      }

      container snmp {
        description "Read-only SNMPv2c monitoring service.";
        leaf enabled {
          type boolean;
          default false;
        }
        leaf listen-address {
          type string;
        }
        leaf port {
          type uint16;
        }
        leaf community {
          type string;
        }
      }
    }
  }

  // ==================================================================
  // Chassis / Clustering Configuration
  // ==================================================================

  container chassis {
    description "Chassis-level HA and clustering configuration.";

    container cluster {
      description "Multi-node cluster settings.";

      leaf enabled {
        type boolean;
        default false;
      }

      list node {
        key "name";
        description "Cluster peer node.";

        leaf name {
          type string;
        }
        leaf address {
          type string;
        }
        leaf priority {
          type uint8;
        }
      }

      container sync {
        description "Cluster synchronization settings.";

        container etcd {
          description "etcd-backed configuration synchronization.";
          leaf-list endpoint {
            type string;
          }
        }
      }
    }
  }

  // ==================================================================
  // Routing Options
  // ==================================================================

  container routing-options {
    description "Global routing configuration options";

    leaf autonomous-system {
      type uint32 {
        range "1..4294967295";
      }
      description "BGP autonomous system number";
    }

    leaf router-id {
      type string {
        pattern '[0-9]+\.[0-9]+\.[0-9]+\.[0-9]+';
      }
      description "Global router ID in dotted decimal notation";
    }

    container static {
      description "Static route configuration";

      list route {
        key "prefix";
        description "Static route entry";

        leaf prefix {
          type string;
          description "Destination network in CIDR format (e.g., 192.168.1.0/24)";
        }

        leaf next-hop {
          type string;
          description "Next-hop IP address";
        }

        leaf distance {
          type uint8 {
            range "1..255";
          }
          default 1;
          description "Administrative distance (metric)";
        }

        leaf bfd {
          type boolean;
          default false;
          description "Enable BFD monitoring for this static route";
        }

        leaf bfd-profile {
          type string;
          description "BFD profile used by this static route";
        }

        leaf bfd-source {
          type string;
          description "Source address used by the static route BFD session";
        }

        leaf bfd-multihop {
          type boolean;
          default false;
          description "Enable multihop BFD for this static route";
        }
      }
    }
  }

  // ==================================================================
  // Routing Instances
  // ==================================================================

  container routing-instances {
    description "Per-instance VRF and L3VPN service configuration.";

    list instance {
      key "name";

      leaf name {
        type string;
      }
      leaf instance-type {
        type enumeration {
          enum vrf;
        }
      }
      leaf route-distinguisher {
        type string;
      }
      leaf vrf-target {
        type string;
      }
      leaf-list vrf-target-import {
        type string;
      }
      leaf-list vrf-target-export {
        type string;
      }
      leaf-list vrf-import {
        type string;
      }
      leaf-list vrf-export {
        type string;
      }
      leaf-list interface {
        type string;
      }
    }
  }

  // ==================================================================
  // Protocols Configuration
  // ==================================================================

  container protocols {
    description "Routing protocol configuration";

    container bfd {
      description "Bidirectional Forwarding Detection configuration.";

      list profile {
        key "name";

        leaf name {
          type string;
        }
        leaf detect-multiplier {
          type uint8 {
            range "2..255";
          }
        }
        leaf receive-interval {
          type uint16 {
            range "10..60000";
          }
        }
        leaf transmit-interval {
          type uint16 {
            range "10..60000";
          }
        }
        leaf echo-mode {
          type boolean;
          default false;
        }
        leaf passive-mode {
          type boolean;
          default false;
        }
      }

      list peer {
        key "address";

        leaf address {
          type string;
        }
        leaf local-address {
          type string;
        }
        leaf interface {
          type string;
        }
        leaf vrf {
          type string;
        }
        leaf multihop {
          type boolean;
          default false;
        }
        leaf profile {
          type string;
        }
        leaf detect-multiplier {
          type uint8 {
            range "2..255";
          }
        }
        leaf receive-interval {
          type uint16 {
            range "10..60000";
          }
        }
        leaf transmit-interval {
          type uint16 {
            range "10..60000";
          }
        }
        leaf echo-mode {
          type boolean;
          default false;
        }
        leaf passive-mode {
          type boolean;
          default false;
        }
        leaf shutdown {
          type boolean;
          default false;
        }
      }
    }

    container bgp {
      description "BGP protocol configuration";

      list group {
        key "name";
        description "BGP peer group";

        leaf name {
          type string;
          description "Group name";
        }

        leaf type {
          type enumeration {
            enum internal {
              description "iBGP peering (same AS)";
            }
            enum external {
              description "eBGP peering (different AS)";
            }
          }
          mandatory true;
          description "BGP group type";
        }

        leaf import {
          type string;
          description "Import policy name (Phase 4: reference to policy-statement)";
        }

        leaf export {
          type string;
          description "Export policy name (Phase 4: reference to policy-statement)";
        }

        list neighbor {
          key "ip";
          description "BGP neighbor configuration";

          leaf ip {
            type string;
            mandatory true;
            description "Neighbor IP address";
          }

          leaf peer-as {
            type uint32 {
              range "1..4294967295";
            }
            mandatory true;
            description "Peer AS number";
          }

          leaf description {
            type string;
            description "Neighbor description";
          }

          leaf local-address {
            type string;
            description "Local address for BGP peering";
          }

          leaf bfd {
            type boolean;
            default false;
            description "Enable BFD failure detection for this neighbor";
          }

          leaf bfd-profile {
            type string;
            description "BFD profile used by this neighbor";
          }
        }
      }
    }

    container ospf {
      description "OSPF protocol configuration";

      leaf router-id {
        type string {
          pattern '[0-9]+\.[0-9]+\.[0-9]+\.[0-9]+';
        }
        description "OSPF router ID (overrides global router-id)";
      }

      list area {
        key "area-id";
        description "OSPF area configuration";

        leaf area-id {
          type string;
          description "OSPF area ID (e.g., 0.0.0.0 or 0)";
        }

        list interface {
          key "name";
          description "Interface in this OSPF area";

          leaf name {
            type string;
            description "Interface name";
          }

          leaf passive {
            type boolean;
            default false;
            description "Passive interface flag";
          }

          leaf metric {
            type uint16 {
              range "1..65535";
            }
            description "OSPF metric for this interface";
          }

          leaf priority {
            type uint8 {
              range "0..255";
            }
            default 1;
            description "OSPF priority for DR election";
          }

          leaf bfd {
            type boolean;
            default false;
            description "Enable BFD failure detection on this interface";
          }

          leaf bfd-profile {
            type string;
            description "BFD profile used by this interface";
          }
        }
      }
    }

    container ospf3 {
      description "OSPFv3 protocol configuration";

      leaf router-id {
        type string {
          pattern '[0-9]+\.[0-9]+\.[0-9]+\.[0-9]+';
        }
        description "OSPFv3 router ID (overrides global router-id)";
      }

      list area {
        key "area-id";
        description "OSPFv3 area configuration";

        leaf area-id {
          type string;
          description "OSPFv3 area ID (e.g., 0.0.0.0 or 0)";
        }

        list interface {
          key "name";
          description "Interface in this OSPFv3 area";

          leaf name {
            type string;
            description "Interface name";
          }

          leaf passive {
            type boolean;
            default false;
            description "Passive interface flag";
          }

          leaf metric {
            type uint16 {
              range "1..65535";
            }
            description "OSPFv3 metric for this interface";
          }

          leaf priority {
            type uint8 {
              range "0..255";
            }
            default 1;
            description "OSPFv3 priority for DR election";
          }

          leaf bfd {
            type boolean;
            default false;
            description "Enable BFD failure detection on this interface";
          }

          leaf bfd-profile {
            type string;
            description "BFD profile used by this interface";
          }
        }
      }
    }

    container mpls {
      description "MPLS forwarding configuration.";

      leaf-list interface {
        type string;
        description "Interface with MPLS forwarding enabled.";
      }
    }

    container vrrp {
      description "VRRP high-availability groups.";

      list group {
        key "name";

        leaf name {
          type string;
        }
        leaf interface {
          type string;
        }
        leaf virtual-address {
          type string;
        }
        leaf priority {
          type uint8;
        }
        leaf preempt {
          type boolean;
          default false;
        }
      }
    }
  }

  // ==================================================================
  // Class of Service
  // ==================================================================

  container class-of-service {
    description "QoS and traffic-control configuration.";

    container forwarding-classes {
      list forwarding-class {
        key "name";
        leaf name {
          type string;
        }
        leaf queue {
          type uint8;
        }
      }
    }

    container traffic-control-profiles {
      list traffic-control-profile {
        key "name";
        leaf name {
          type string;
        }
        leaf shaping-rate {
          type uint64;
        }
        leaf scheduler-map {
          type string;
        }
      }
    }

    container interfaces {
      list interface {
        key "name";
        leaf name {
          type string;
        }
        leaf output-traffic-control-profile {
          type string;
        }
      }
    }
  }

  // ==================================================================
  // Security
  // ==================================================================

  container security {
    description "Management-plane security settings exposed through NETCONF XML.";

    container netconf {
      container ssh {
        leaf port {
          type uint16;
        }
      }
    }

    container rate-limit {
      leaf per-ip {
        type uint16;
      }
      leaf per-user {
        type uint16;
      }
    }
  }

  // ==================================================================
  // IETF Interfaces Extension (Augmentation)
  // ==================================================================

  augment "/if:interfaces/if:interface" {
    description "Extend IETF interfaces with Arca-specific attributes";

    // Note: 'description' is already defined in ietf-interfaces, so we don't redeclare it
    // Instead, we rely on the IETF model's description leaf

    container units {
      description "Logical units (sub-interfaces) for this interface";

      list unit {
        key "unit-id";
        description "Logical unit configuration";

        leaf unit-id {
          type uint32;
          description "Unit number (e.g., 0 for ge-0/0/0.0)";
        }

        container family {
          description "Address family configuration";

          container inet {
            description "IPv4 address family";

            leaf-list address {
              type string;
              description "IPv4 address in CIDR format";
            }
          }

          container inet6 {
            description "IPv6 address family";

            leaf-list address {
              type string;
              description "IPv6 address in CIDR format";
            }
          }
        }
      }
    }
  }

  // ==================================================================
  // Operational State
  // ==================================================================

  container state {
    config false;
    description "Operational state data (read-only)";

    container interfaces {
      description
        "Arca-specific interface operational state. NETCONF <get> also
         exposes live interface status, counters, and VPP queue placement
         through ietf-interfaces.";
    }

    container routes {
      description "Live IPv4 and IPv6 route table entries.";

      list route {
        description "One route entry or nexthop path.";

        leaf prefix {
          type string;
          description "Route destination prefix.";
        }
        leaf next-hop {
          type string;
          description "Route nexthop address.";
        }
        leaf protocol {
          type string;
          description "Protocol that installed the route.";
        }
        leaf metric {
          type uint32;
          description "Route metric.";
        }
        leaf interface {
          type string;
          description "Outgoing interface.";
        }
        leaf active {
          type boolean;
          description "Whether the path is active in FRR.";
        }
      }
    }

    container routing-instances {
      description "Running routing-instance intent and VPP table bindings.";

      list instance {
        key "name";
        description "Per-routing-instance table mapping and policy summary.";

        leaf name {
          type string;
          description "Routing-instance name.";
        }
        leaf instance-type {
          type string;
          description "Routing-instance type.";
        }
        leaf route-distinguisher {
          type string;
          description "Configured route distinguisher.";
        }
        leaf ipv4-table-id {
          type uint32;
          description "Bound VPP IPv4 table ID.";
        }
        leaf ipv6-table-id {
          type uint32;
          description "Bound VPP IPv6 table ID.";
        }
        leaf-list import-target {
          type string;
          description "VPN import route target.";
        }
        leaf-list export-target {
          type string;
          description "VPN export route target.";
        }
        leaf-list import-policy {
          type string;
          description "Ordered import policy chain.";
        }
        leaf-list export-policy {
          type string;
          description "Ordered export policy chain.";
        }
        leaf-list interface {
          type string;
          description "Interface bound to the routing-instance tables.";
        }
      }
    }

    container protocols {
      description "Protocol operational state.";

      container bgp {
        description "BGP neighbor operational state.";

        list neighbor {
          description "Per-neighbor BGP operational state.";

          leaf peer-address {
            type string;
            description "BGP peer address.";
          }
          leaf peer-as {
            type uint32;
            description "Remote peer AS number.";
          }
          leaf state {
            type string;
            description "BGP finite-state-machine state.";
          }
          leaf uptime-seconds {
            type uint64;
            description "Peer uptime in seconds.";
          }
          leaf prefix-received {
            type uint32;
            description "Received prefix count.";
          }
          leaf prefix-sent {
            type uint32;
            description "Sent prefix count.";
          }
        }
      }

      container ospf {
        description "OSPFv2 neighbor operational state.";

        list neighbor {
          description "Per-neighbor OSPFv2 operational state.";

          leaf router-id {
            type string;
            description "OSPF neighbor router ID.";
          }
          leaf address {
            type string;
            description "OSPF neighbor address.";
          }
          leaf interface {
            type string;
            description "Interface associated with the adjacency.";
          }
          leaf state {
            type string;
            description "OSPF adjacency state.";
          }
          leaf role {
            type string;
            description "Neighbor role reported by FRR.";
          }
          leaf priority {
            type uint32;
            description "OSPF neighbor priority.";
          }
          leaf dead-time-seconds {
            type uint64;
            description "Remaining dead timer in seconds.";
          }
          leaf uptime-seconds {
            type uint64;
            description "Adjacency uptime in seconds.";
          }
        }
      }

      container ospf3 {
        description "OSPFv3 neighbor operational state.";

        list neighbor {
          description "Per-neighbor OSPFv3 operational state.";

          leaf router-id {
            type string;
            description "OSPFv3 neighbor router ID.";
          }
          leaf address {
            type string;
            description "OSPFv3 neighbor address.";
          }
          leaf interface {
            type string;
            description "Interface associated with the adjacency.";
          }
          leaf state {
            type string;
            description "OSPFv3 adjacency state.";
          }
          leaf role {
            type string;
            description "Neighbor role reported by FRR.";
          }
          leaf priority {
            type uint32;
            description "OSPFv3 neighbor priority.";
          }
          leaf dead-time-seconds {
            type uint64;
            description "Remaining dead timer in seconds.";
          }
          leaf uptime-seconds {
            type uint64;
            description "Adjacency uptime in seconds.";
          }
        }
      }

      container bfd {
        description "Cached BFD convergence state and failure counters.";

        leaf last-run {
          type string;
          description "RFC3339 timestamp of the latest BFD state collection.";
        }
        leaf configured-peers {
          type uint32;
          description "Number of BFD peers expected from configuration.";
        }
        leaf observed-peers {
          type uint32;
          description "Number of BFD peers observed in FRR runtime state.";
        }
        leaf up-peers {
          type uint32;
          description "Number of observed BFD peers in up state.";
        }
        leaf down-peers {
          type uint32;
          description "Number of configured or observed BFD peers not up.";
        }
        leaf session-down-events {
          type uint64;
          description "Aggregate BFD session down events.";
        }
        leaf rx-fail-packets {
          type uint64;
          description "Aggregate BFD RX failure packet counter.";
        }
        list peer {
          description "Per-peer BFD operational state.";

          leaf address {
            type string;
            description "BFD peer address.";
          }
          leaf local-address {
            type string;
            description "Local address used for the BFD session.";
          }
          leaf interface {
            type string;
            description "Interface associated with the BFD session.";
          }
          leaf vrf {
            type string;
            description "VRF associated with the BFD session.";
          }
          leaf status {
            type string;
            description "FRR BFD peer status.";
          }
          leaf diagnostic {
            type string;
            description "Local BFD diagnostic string.";
          }
          leaf remote-diagnostic {
            type string;
            description "Remote BFD diagnostic string.";
          }
          leaf observed {
            type boolean;
            description "Whether FRR reported the peer.";
          }
          leaf up {
            type boolean;
            description "Whether the peer is currently up.";
          }
          leaf session-down-events {
            type uint64;
            description "Peer session down event counter.";
          }
          leaf rx-fail-packets {
            type uint64;
            description "Peer RX failure packet counter.";
          }
        }
        leaf-list issue {
          type string;
          description "Convergence issue detected by arca-routerd.";
        }
        leaf last-error {
          type string;
          description "Last BFD state collection error.";
        }
      }
    }
  }
}
